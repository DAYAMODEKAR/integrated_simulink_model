# integrated_requirements

## integrated_requirements: References to integrated_requirements.docx (Container)
Read-only references to Microsoft Word document.

### Advanced AirBag Deployment System requirements (Functional)

#### Input Scaling (Functional)

##### Simulink_requirement_item_1: Ignition should be ON primarily ... (Functional)
Ignition should be ON primarily for the system to be enabled.

##### Seat Belt Status to be ON after: Seat Belt Status to be ON after ... (Functional)
Seat Belt Status to be ON after the ignition is set indicating front seat occupied
Weight Sensor detects the weight of driver seated.
Distance gives the distance between the driver and airbag situated in front for safe deployment.
Accelerometer reading to detect the severity of crash by find vehicle speed.

#### Occupant Detection System (Functional)

##### pi_ctrl_1: Oc_det_1. Must implement Seatbel... (Functional)
Oc_det_1. Must implement Seatbelt tensioning control algorithm based on weight sensor.

##### Oc_det_2. Should provide an outp: Oc_det_2. Should provide an outp... (Functional)
Oc_det_2. Should provide an output enable signal which is an input to airbag deployment subsystem.

#### Safe Distance Enable system (Functional)
Safe Distance Enable system
sf_dst_1. Must implement safe distance algorithm based on distance input.
sf_dst_2. Should provide an output enable signal which is an input to airbag deployment subsystem.

#### Airbag Decision System (Functional)

##### pwm_1: Abds_1. Based on two enable inpu... (Functional)
Abds_1. Based on two enable inputs from other system the system should be enabled.

##### Abds_2. Based on vehicle velocit: Abds_2. Based on vehicle velocit... (Functional)
Abds_2. Based on vehicle velocity and speed detect the severity of crash and set seat belt,airbag and steering retraction system.

#### Output Scaling (Functional)

##### out_scl_2: Seat belt tensioning percent set... (Functional)
Seat belt tensioning percent set at the time of seat occupied to be set.

##### Airbag deployment and steering r: Airbag deployment and steering r... (Functional)
Airbag deployment and steering retraction status using Boolean values.
Seat belt tensioning status display.
Vehicle Speed Display.

### Seat belt System Requirements (Functional)

#### Input Scaling: (Functional)
Input Scaling:
One input comes from seat occupied sensor (pressure sensor) for seat-occupied.
One input comes from seat belt sensor.
Inputs values should be either zero or one only.

#### Chart: (Functional)

##### Simulink_requirement_item_5: Ch_01: (Functional)
Ch_01: Output values comes either zero or one only.

##### Ch_02: (Functional)
Ch_02: When seat occupied and seat belt input is both 0 then output should zero for all three outputs.
Ch_03: When seat occupied status is zero and seat belt input is 1 then output should zero for all three outputs.

##### Simulink_requirement_item_6: Ch_04: (Functional)
Ch_04: When seat occupied status is one and seat belt input is 1 then seat_occupied_out is one and seat_belt_out is one and buzzer should be zero.

##### Simulink_requirement_item_7: Ch_05: (Functional)
Ch_05: When seat occupied status is one and seat belt input is 0 then seat_occupied_out is one and seat_belt_out is zero and buzzer should be one.

#### Out scaling: (Functional)

##### Simulink_requirement_item_2: Output for seat occupied status. (Functional)

##### Simulink_requirement_item_3: Output for seatbelt on or off status. (Functional)

##### Simulink_requirement_item_4: Output for seatbelt off status. (Functional)

##### <?> (Functional)

### Semi Active Suspension System Requirements (Functional)

#### Input Scaling_1: Input Scaling (Functional)
Input Scaling
Ignition should be ON primarily for the system to be enabled.
Input from the mode selector switch signifying the mode in which the vehicle is currently operating.
Detects the pressure inside suspension chamber.
Accelerometer reading to detect the hard acceleration or hard de-acceleration of the vehicle.

#### Chart: Valve actuator (Functional)
Chart: Valve actuator
Cva_1: Checks whether the ignition is on or off.
Cva_2: If ignition is off the system is turned off and there is no output.
Cva_3: Checks the pressure input.
Cva_4: If the pressure is low then the (Front input valves) F_i_v and (Rear input valves) R_i_v are
Cva_5: If the pressure is high then the (Front output valves) F_o_v and (Rear output valves) R_o_v are 1
Cva_6: If the pressure is ideal then all the outputs are 0.
Cva_7: If the pressure is ideal and acceleration input is < 30 then F_i_v is 1.
Cva_8: If the pressure is ideal and acceleration input is > 30 and <60 then all outputs are 0.
Cva_9: If the pressure is ideal and acceleration input is >60 then R_i_v is 1.

#### Output Scaling_1: Output Scaling (Functional)
Output Scaling
Lamp to indicate ignition on or off.
Lamp to indicate the mode in which the vehicle is currently operating.
(Front input valves) F_i_v and (Rear input valves) R_i_v to actuate the input valves.
(Front output valves) F_o_v and (Rear output valves) R_o_v to actuate the output valves.

### Passive Keyless Entry System Requirements (Functional)

#### Input Scaling_2: Input Scaling (Functional)
Input Scaling
Door Signal goes from 0 to 200
Vehicle signal goes from 100 to 750
Vehicle signal comes from 1000 to 100
Door signal comes from 200 to 0

#### Keyless Entry System (Functional)
Keyless Entry System
Key_en_1. When signal ranges from 0 to 100, door status toggles from lock to unlock
Key_en_2. The lock enables when signal exceed 750 count
Key_en_3. When signal comes from 1000 to 100, the door status remains same but value is shown as different one
Key_en_4. When the signal ranges from 100 to 0, the door toggles its status to unlock

#### Output Scaling_2: Output Scaling (Functional)
Output Scaling
The door status changes only once for signal increasing beyond 750
The door status goes to 2 or 3 value when inside vehicle signal value range
Door status goes to 1 or 0 when inside door signal value range
